RFID-MON-MIB DEFINITIONS ::= BEGIN

IMPORTS
    MODULE-IDENTITY, OBJECT-TYPE, Integer32, experimental,
    NOTIFICATION-TYPE                       FROM SNMPv2-SMI
    SnmpAdminString                         FROM SNMP-FRAMEWORK-MIB
    RowStatus, StorageType, DisplayString,
    TruthValue                              FROM SNMPv2-TC
    InetAddressType, InetAddress            FROM INET-ADDRESS-MIB
;

-- MODLUE IDENTITY: rfidMon
-- REVISION e LAST-UPDATED sao datas no formato AAAAMMDDHHMM
-- Tem de haver um REVISION igual a LAST-UPDATED (problema da aula)

containershipMIB MODULE-IDENTITY
    LAST-UPDATED "201811161430Z" -- tem de ter REVISION com esta data!
    ORGANIZATION "www.di.uminho.pt"
    CONTACT-INFO
	 "postal:   Departamento de Informatica
                Campus de Gualtar
                4710-057 BRAGA
                Portugal
      email:    gestao-redes@di.uminho.pt"
    DESCRIPTION
	    "MIB objects for Container Creation"
    REVISION     "201811161430Z"  -- tem de ser igual a LAST-UPDATE!
    DESCRIPTION
        "Primeira versao"
    ::= { experimental 6000 }

-- TOP LEVEL STRUCTURS
containershipParam       OBJECT IDENTIFIER ::= { containershipMIB 1 }
containershipImage       OBJECT IDENTIFIER ::= { containershipMIB 2 }
containershipContainer   OBJECT IDENTIFIER ::= { containershipMIB 3 }
containershipStatus     OBJECT IDENTIFIER ::= { containershipMIB 4 }
containershipSecurity     OBJECT IDENTIFIER ::= { containershipMIB 5 }
--
-- scalars: zonaId, zonaDesc, nAreas...
--

--
-- Para o containershipParams
--

containershipParamImage OBJECT-TYPE
    SYNTAX      Integer32
    MAX-ACCESS  read-write
    STATUS      current
    DESCRIPTION
	"Indice da imagem (na tabela)"
    ::= { containershipParam 1 }

containershipParamContainer OBJECT-TYPE
    SYNTAX      DisplayString
    MAX-ACCESS  read-write
    STATUS      current
    DESCRIPTION
    "Nome do container responsavel pela imagem"
    ::= { containershipParam 2 }

containershipParamFlag OBJECT-TYPE
    SYNTAX      Integer32
    MAX-ACCESS  read-write
    STATUS      current
    DESCRIPTION
	"Flag para indicar se esta concluido. 0 nao esta concluido, 1 esta concluido"
    ::= { containershipParam 3 }

--
-- containershipImageTable
-- grupo das tabelas de imagnes disponiveis
--

containershipImageNumber OBJECT-TYPE
    SYNTAX      Integer32
    MAX-ACCESS  read-only
    STATUS      current
    DESCRIPTION
	"Contem o numero de imagens existentes na mib"
    ::= { containershipImage 1 }

containershipImageTable OBJECT-TYPE
    SYNTAX      SEQUENCE OF ContainershipImageEntry
    MAX-ACCESS  not-accessible
    STATUS      current
    DESCRIPTION
	"Tabela com as diferentes imagens existentes"
    ::= { containershipImage 2 }

containershipImageEntry OBJECT-TYPE
    SYNTAX      ContainershipImageEntry
    MAX-ACCESS  not-accessible
    STATUS      current
    DESCRIPTION
	"Linha para cada entrada da tabela (para cada imagem)"
    INDEX   { ContainershipImageIndex }
    ::= { containershipImageTable 1 }

ContainershipImageEntry ::= SEQUENCE {
    ContainershipImageIndex  Integer32,
    ContainershipImageName DisplayString
}

ContainershipImageIndex OBJECT-TYPE
    SYNTAX      Integer32 (0..100)
    MAX-ACCESS  read-only
    STATUS      current
    DESCRIPTION
	"Indice de cada imagem da tabela"
    ::= { containershipImageEntry 1 }

ContainershipImageName OBJECT-TYPE
    SYNTAX      DisplayString
    MAX-ACCESS  read-only
    STATUS      current
    DESCRIPTION
    "Nome da imagem"
    ::= { containershipImageEntry 2 }

--
-- containershipContainerTable
--


-- DUVIDA DUVIDA DUVIDA DUVIDA DUVIDA ============================?
-- Nao deveria de ser read create? Como é que criamos entao uma nova entrada na tabela?

containershipContainerNumber OBJECT-TYPE
    SYNTAX      Integer32
    MAX-ACCESS  read-only
    STATUS      current
    DESCRIPTION
	"Contem o numero de containers existentes na mib"
    ::= { containershipContainer 1 }

containershipContainerTable OBJECT-TYPE
    SYNTAX      SEQUENCE OF ContainershipContainerEntry
    MAX-ACCESS  not-accessible
    STATUS      current
    DESCRIPTION
	"Tabela com os containers que foram criados"
    ::= { containershipContainer 2 }

containershipContainerEntry OBJECT-TYPE
    SYNTAX      ContainershipContainerEntry
    MAX-ACCESS  not-accessible
    STATUS      current
    DESCRIPTION
	"Linha para cada entrada da tabela"
    INDEX   { containershipContainerIndex }
    ::= { containershipContainerTable 1 }

ContainershipContainerEntry ::= SEQUENCE {
    containershipContainerIndex  Integer32,
    containershipContainerName   DisplayString,
    containershipContainerImage     Integer32,
    containershipContainerStatus      DisplayString,
    containershipContainerProcessor   Integer32
}

containershipContainerIndex OBJECT-TYPE
    SYNTAX      Integer32(0..100)
    MAX-ACCESS  read-only
    STATUS      current
    DESCRIPTION
	"Indice de cada linha da tabela"
    ::= { containershipContainerEntry 1 }

containershipContainerName OBJECT-TYPE
    SYNTAX      DisplayString
    MAX-ACCESS  read-only
    STATUS      current
    DESCRIPTION
	"Nome do container"
    ::= { containershipContainerEntry 2 }

containershipContainerImage OBJECT-TYPE
    SYNTAX      Integer32
    MAX-ACCESS  read-only
    STATUS      current
    DESCRIPTION
	"ID da imagem que esta criada no container"
    ::= { containershipContainerEntry 3 }

containershipContainerStatus OBJECT-TYPE
    SYNTAX      DisplayString
    MAX-ACCESS  read-write
    STATUS      current
    DESCRIPTION
	"Estado atual do container"
    ::= { containershipContainerEntry 4 }

containershipContainerProcessor OBJECT-TYPE
    SYNTAX      DisplayString
    MAX-ACCESS  read-only
    STATUS      current
    DESCRIPTION
	"Percentagem de utilizacao do processador"
    ::= { containershipContainerEntry 5 }

--
-- Escalaraes do status
-- vamos colocar todos os nomes começados por "status"
--

containershipStatusIniciate OBJECT-TYPE
    SYNTAX      DisplayString
    MAX-ACCESS  read-only
    STATUS      current
    DESCRIPTION
	"Data de inicio do agente"
    ::= { containershipStatus 1 }

containershipStatusLastContainer OBJECT-TYPE
    SYNTAX      DisplayString
    MAX-ACCESS  read-only
    STATUS      current
    DESCRIPTION
	"Data da última criação de um container"
    ::= { containershipStatus 2 }

containershipSecurityPeriodo OBJECT-TYPE
    SYNTAX      Integer32
    MAX-ACCESS  read-write
    STATUS      current
    DESCRIPTION
	"Periodo de reset dos contadores dos limites"
    ::= { containershipSecurity 1 }

containershipSecurityInstantLimit OBJECT-TYPE
    SYNTAX      Integer32
    MAX-ACCESS  read-write
    STATUS      current
    DESCRIPTION
    "Limite de pacotes processados por Período"
    ::= { containershipSecurity 2 }

containershipSecurityMomentLimit OBJECT-TYPE
    SYNTAX      Integer32
    MAX-ACCESS  read-write
    STATUS      current
    DESCRIPTION
	"Limite médio de pacotes processados nos últimos 4 Periodos"
    ::= { containershipSecurity 3 }

containershipSecurityTemporalLimit OBJECT-TYPE
    SYNTAX      Integer32
    MAX-ACCESS  read-write
    STATUS      current
    DESCRIPTION
	"Limite médio de pacotes processados no tempo de execussão do programa"
    ::= { containershipSecurity 4 }

END
