RFID-MON-MIB DEFINITIONS ::= BEGIN

IMPORTS
    MODULE-IDENTITY, OBJECT-TYPE, Integer32, experimental,
    NOTIFICATION-TYPE                       FROM SNMPv2-SMI
    SnmpAdminString                         FROM SNMP-FRAMEWORK-MIB
    RowStatus, StorageType, DisplayString,
    TruthValue                              FROM SNMPv2-TC
    InetAddressType, InetAddress            FROM INET-ADDRESS-MIB
;

-- MODLUE IDENTITY: rfidMon
-- REVISION e LAST-UPDATED sao datas no formato AAAAMMDDHHMM
-- Tem de haver um REVISION igual a LAST-UPDATED (problema da aula)

rfidMon MODULE-IDENTITY
    LAST-UPDATED "201811161430Z" -- tem de ter REVISION com esta data!
    ORGANIZATION "www.di.uminho.pt"
    CONTACT-INFO    
	 "postal:   Departamento de Informatica
                Campus de Gualtar
                4710-057 BRAGA
                Portugal
      email:    gestao-redes@di.uminho.pt"
    DESCRIPTION
	    "MIB objects for RFID Monitoring"
    REVISION     "201811161430Z"  -- tem de ser igual a LAST-UPDATE!
    DESCRIPTION
        "Primeira versao"
    ::= { experimental 2018 }

--
-- scalars: zonaId, zonaDesc, nAreas...
--

zonaId OBJECT-TYPE
    SYNTAX      Integer32
    MAX-ACCESS  read-write
    STATUS      current
    DESCRIPTION
	"Identificador da zona de trabalho da oficina"
    ::= { rfidMon 1 }

zonaDescr OBJECT-TYPE
    SYNTAX      DisplayString
    MAX-ACCESS  read-write
    STATUS      current
    DESCRIPTION
	"Descricao da zona de trabalho da oficina"
    ::= { rfidMon 2 }

nAreas OBJECT-TYPE
    SYNTAX      Integer32
    MAX-ACCESS  read-write
    STATUS      current
    DESCRIPTION
	"Numero de areas da zona de trabalho da oficina"
    ::= { rfidMon 3 }

--
--  Tables: rfidTable, ...
--

rfidTable OBJECT-TYPE
    SYNTAX      SEQUENCE OF RFIDTableEntry
    MAX-ACCESS  not-accessible
    STATUS      current
    DESCRIPTION
	"Esta tabela contem as tags RFID existente em cada area... 
     Tabela de areas dentro da ZONA"
    ::= { rfidMon 4 }

rfidTableEntry OBJECT-TYPE
    SYNTAX      RFIDTableEntry
    MAX-ACCESS  not-accessible
    STATUS      current
    DESCRIPTION
	"Um linha da tabela de areas... "
    INDEX   { areaId }
    ::= { rfidTable 1 }

RFIDTableEntry ::= SEQUENCE {
    areaId  Integer32,
    areaDescr   DisplayString,
    operational TruthValue, -- nao existe BOOLEAN no SMIv2! 
    tag     OCTET STRING
}
-- BOOLEAN eh uma keyword do ASN.1 nao consta no SMI...
-- TruthValue e' o que deve ser usado (INTEGER 0 ou 1)

areaId OBJECT-TYPE
    SYNTAX      Integer32 (1..32)
    MAX-ACCESS  read-write
    STATUS      current
    DESCRIPTION
	"Identificador da area (unico) "
    ::= { rfidTableEntry 1 }

areaDescr OBJECT-TYPE
    SYNTAX      DisplayString
    MAX-ACCESS  read-write
    STATUS      current
    DESCRIPTION
	"Descricao da area "
    ::= { rfidTableEntry 2 }
 
operational OBJECT-TYPE
    SYNTAX      TruthValue
    MAX-ACCESS  read-write
    STATUS      current
    DESCRIPTION
	"Boolean true or false se a area estiver operacional "
    ::= { rfidTableEntry 3 }
 
tag OBJECT-TYPE
    SYNTAX      OCTET STRING (SIZE(6))
    MAX-ACCESS  read-write
    STATUS      current
    DESCRIPTION
	"Valor da etiqueta RFID que foi lido pelo leitor"
    ::= { rfidTableEntry 4 }
 
END
